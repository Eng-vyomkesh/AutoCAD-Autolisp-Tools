(defun c:TL (/ ss i total ent obj len)
  (vl-load-com)
  (setq total 0.0)
  (princ "\nSelect lines, polylines, or arcs to sum their total length:")
  (setq ss (ssget '((0 . "LINE,LWPOLYLINE,POLYLINE,ARC"))))
  (if ss
    (progn
      (repeat (setq i (sslength ss))
        (setq ent (ssname ss (setq i (1- i))))
        (setq obj (vlax-ename->vla-object ent))
        (cond
          ((vlax-property-available-p obj 'Length)
           (setq total (+ total (vla-get-Length obj))))
          ((vlax-property-available-p obj 'ArcLength)
           (setq total (+ total (vla-get-ArcLength obj))))
        )
      )
      (princ (strcat "\n>>> Total Length of Selected Pipes/Lines = " (rtos total 2 2) " <<<"))
      (alert (strcat "Total Length: " (rtos total 2 2)))
    )
    (princ "\nNo valid lines or pipes selected.")
  )
  (princ)
)
(princ "\nLoaded successfully! Type TL to run the Total Length command.")
(princ)
